module odl-distribution-version {
    yang-version 1;
    namespace "urn:opendaylight:params:xml:ns:yang:integration:distribution:version";
    prefix "odl-version";

    import config { prefix config; revision-date 2013-04-05; }

    description
        "Piece of ODL configuration holding version strings for ODL components.";

    revision "2016-03-16" {
        description
            "Initial revision";
    }

    identity odl-version {
        base config:module-type;
    }

    augment "/config:modules/config:module/config:configuration" {
        case odl-version {
            when "/config:modules/config:module/config:type = 'odl-version'";
            leaf version {
                description "Short string with version of component corresponding to module name.";
                type string;
                mandatory true;
            }
            list test {
                description "Test to see whether config-subsystem accepts empty lists from XML.";
                key "foo bar";
                leaf foo {
                    type string;
                }
                leaf bar {
                    type string;
                }
            }
        }
    }
}
